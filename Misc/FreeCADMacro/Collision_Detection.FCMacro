try:
    from PySide2 import QtCore
    from PySide2.QtWidgets import QMessageBox
except ImportError:
    from PySide import QtCore
    from PySide.QtGui import QMessageBox

import FreeCAD as app
import FreeCADGui as gui


def error_dialog(msg):
    """Create a simple dialog QMessageBox with an error message."""
    app.Console.PrintError(msg + '\n')
    diag = QMessageBox(QMessageBox.Icon.Critical, 'Error in macro HighlightCommon', msg)
    diag.setWindowModality(QtCore.Qt.ApplicationModal)
    diag.exec_()


def main():
    if len(gui.Selection.getSelection()) < 2:
        error_dialog('Select at least two objects')
        return

    object_list = []
    for obj in gui.Selection.getSelection():
        if obj not in object_list:
            object_list.append(obj)

    for i, object_a in enumerate(object_list):
        for object_b in object_list[(i + 1):]:
            shape_a = object_a.Shape
            shape_b = object_b.Shape
            label_a = object_a.Label
            label_b = object_b.Label
            common = shape_a.common(shape_b)
            if common.Volume > 1e-6:
                app.Console.PrintMessage(
                    'Volume of the intersection between {} and {}: {}\n'.format(
                        label_a,
                        label_b,
                        common.Volume))

                intersection_object = app.activeDocument().addObject(
                    'Part::Feature')
                intersection_object.Label = 'Common ({} - {})'.format(
                    label_a, label_b)
                intersection_object.Shape = common
                intersection_object.ViewObject.ShapeColor = (1.0, 0.0, 0.0, 1.0)
                object_a.ViewObject.Transparency = 80
                object_b.ViewObject.Transparency = 80
            else:
                app.Console.PrintMessage(
                    'No intersection between {} and {}\n'.format(
                        label_a,
                        label_b))


if __name__ == '__main__':
    main()
